AES-256-V71-DATAVIEW DEFINITIONS ::=
BEGIN

   -- Interfaces to the external cryptographic functions
   -- (required interfaces aes256_encrypt_block and cmac256)

   -- AES-256 key
   AES256-Key ::= OCTET STRING (SIZE (32))

   -- One 16-octet AES block
   AES-Block ::= OCTET STRING (SIZE (16))

   -- Result of a call to an external cryptographic function
   Crypto-Status ::= ENUMERATED {
       ok,
       failed
   }

   -- AES-256 uses 256-bit key
   AES256Key ::= OCTET STRING (SIZE (32))
   AES256ExpandedKey ::= OCTET STRING (SIZE (240))

   -- AES uses 128-bit blocks
   AES256Block ::= OCTET STRING (SIZE (16))

   -- AES encrypts buffers 16-bytes at a time
   AES256Buffer ::= OCTET STRING (SIZE (16))

   -- Some AES modes of operation operate on variable length buffers. Must put upper bound on type though for ASN.1
   AES256VariableLengthBuffer ::= OCTET STRING (SIZE (0..2048))

   AES256Context ::= SEQUENCE
   {
      expandedKey AES256ExpandedKey
   }

   AES256ECBContext ::= SEQUENCE
   {
      aes256Ctx AES256Context
   }

   AES256CBCContext ::= SEQUENCE
   {
      aes256Ctx AES256Context,
      iv AES256Block
   }

   AES256CTRContext ::= SEQUENCE
   {
      aes256Ctx AES256Context,
      iv AES256Block
   }

END

TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

T-Runtime-Error ::= CHOICE {
   noerror T-UInt32, -- this shall be NULL, but DMT does not support NULL and SEDS does not support empty sequences
   encodeerror T-Int32, -- the names shall be changed after fix in seds converter (space creator) will be merged
   decodeerror T-Int32
}

END

-- Dataview generated on-the-fly providing information on the system
-- and made available to the user code.
System-Dataview DEFINITIONS ::=
BEGIN

   -- Range of PID - type can be used to size arrays of PID type
   PID-Range ::= INTEGER(0..6)

   -- List of functions (instances) present in the system
   PID ::= ENUMERATED {
       aes256,
       
       aes256cbc,
       
       aes256ctr,
       
       aes256ecb,
       
       testharness,
       
       uartotherend,
       
       
       env
   }

END
